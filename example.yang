module example {
  yang-version 1.1;
  namespace "urn:example:example";
  prefix "ex";
  revision "2026-08-12";
  container server {
    choice protocol {
      case tcp {
        container tcp {
          leaf port {
            type uint8;
          }
        }
      }
      case udp {
        container udp {
          leaf port {
            type uint8;
          }
        }
      }
    }
  }
}
